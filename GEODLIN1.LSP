(defun c:geodlin()
        (setvar "cmdecho" 0)
        (command "ucs" "w")
        (setq stosn (getvar "osmode"))
        (setq stsmu (getvar "angdir"))
        (setq storj (getvar "angbase"))
        (setq oldla (getvar "clayer"))
        (setvar "osmode" 0)
        (setvar "angdir" 0)
        (setvar "angbase" 0.0000)
        (prompt "\nPokazite jednu liniju")
        (initget 1)
        (setq en (car (entsel "\nkoja se prevodi u geodetsku liniju:")))
        (setq ed (entget en))
        (setq lay (cdr(assoc 8 ed)))
        (setq ss (ssget "x" (list (cons 0 "line")(cons 8 lay))))
        (setq ssluk (ssget "x" (list (cons 0 "arc")(cons 8 lay))))
        (if ss (setq n (sslength ss)) (setq n 0))
        (if ssluk (setq nl (sslength ssluk)) (setq nl 0))
        (initget 1)
        (setq razm (getdist "\nZa koliko se skracuje linija = "))
        (setq odg (strcase(getstring "\nDa li se crtaju tacke (D/N):<D>")))
        (command "layer" "m" "geodlin" "")
        (setq i 0)
        (while (< i n)
                (setq en (ssname ss i))
                (setq ed (entget en))
                (setq pt1 (cdr(assoc 10 ed)))
                (setq pt2 (cdr(assoc 11 ed)))
		(setq d (distance pt1 pt2))
                (setq ugao1 (angle pt1 pt2))
                (setq ugao2 (angle pt2 pt1))
                (setq pt1n (polar pt1 ugao1 razm))
                (setq pt2n (polar pt2 ugao2 razm))
                (if (> d (* 2.0 razm))
	                (command "line" pt1n pt2n "")
		)
                (if (or (= odg "")(= odg "D"))
                        (progn
                         (if (not (osnap pt1 "node"))
                         (command "point" pt1))
                         (if (not (osnap pt2 "node"))
                         (command "point" pt2))
                        )
                )
                (setq i (1+ i))
        )
        (setq i 0)
        (while (< i nl)
                (setq en (ssname ssluk i))
                (setq ed (entget en))
                (setq ugstart (cdr (assoc 50 ed)))
                (setq ugkraj (cdr (assoc 51 ed)))
                (setq centar (cdr (assoc 10 ed)))
                (setq r (cdr (assoc 40 ed)))
                (setq delta (/ razm r))
                (setq ugsn (+ ugstart delta))
                (setq ugkn (- ugkraj delta))
                (setq pt1 (polar centar ugstart r))
                (setq pt2 (polar centar ugkraj r))
                (if (or (= odg "")(= odg "D"))
                        (progn
                         (if (not (osnap pt1 "node"))
                         (command "point" pt1))
                         (if (not (osnap pt2 "node"))
                         (command "point" pt2))
                        )
                )
                (setq d (- ugkraj ugstart))
                (if (< d 0) (setq d (+ d (* 2.0 pi))))
                (setq trt (+ ugstart (/ d 2.0)))
                (setq d (* r d))
                (if (> d (* 2.0 razm))
                (progn
                 (command "copy" en "" centar centar)
                 (setq en (entlast))
                 (setq ed (entget en))
                 (setq ed (subst(cons 8 "geodlin")(assoc 8 ed) ed))
                 (entmod ed)
                 (entupd en)
                 (setq ed (subst(cons 50 ugsn)(assoc 50 ed) ed))
                 (entmod ed)
                 (entupd en)
                 (setq ed (subst(cons 51 ugkn)(assoc 51 ed) ed))
                 (entmod ed)
                 (entupd en)
                )
                (progn
                   (setq ptm (polar centar trt r))
                   (command "point" ptm)
                )
               )
               (setq i (1+ i))
        )
        (command "layer" "s" oldla "")
        (setvar "osmode" stosn)
        (setvar "angdir" stsmu)
        (setvar "angbase" storj)
        (setvar "cmdecho" 1)
        (princ)
)
