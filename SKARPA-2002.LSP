(defun c:sk ()
  (setq var 0)
  (setvar "cmdecho" var)
  (setq oldos (getvar "osmode"))
  (setvar "osmode" 0)
  (command "ucs" "w")
  (setq oldla (getvar "clayer"))
	(if (not(tblsearch "layer" "skarpa"))
		(command "layer" "n" "skarpa" "")
	)
  (command "layer" "s" "skarpa" "")
  (if (not dist)
    (progn
       (initget (+ 1 2 4))
       (setq dist (getreal "\nUnesi rastojanje izmedju linija srafure: "))
       (initget (+ 1 2 4))
       (setq dkratka (getdist "\nUnesi duzinu kratkih linija srafure:"))
    );then
  );if
  (initget 1)
  (setq elm1 (car (entsel "\nOdaberi element od koga se crta srafura skarpe: ")))
  (redraw elm1 3)
  (initget 1)
  (setq elm2 (car (entsel "\nOdaberi element do koga se crta srafura skarpe: ")))
  (redraw elm2 3)
	(setq
     ent1 (entget elm1)
     tipent1 (cdr (assoc 0 ent1))
        ent2 (entget elm2)
     tipent2 (cdr (assoc 0 ent2))
	)
	(cond
		((/= tipent1 "LINE")
			(princ "\nPrvi entitet nije LINE!")
			(princ)
			(exit)
		)
		((/= tipent2 "LINE")
				(princ "\Drugi entitet nije LINE!")
				(princ)
				(exit)
		)
	)
	(setq 
		p11 (cdr(assoc 10 ent1))
		y11 (car p11)
		x11 (cadr p11)
		p11 (list y11 x11 0.0)
		p12 (cdr(assoc 11 ent1))
		y12 (car p12)
		x12 (cadr p12)
		p12 (list y12 x12 0.0)
		u11 (angle p11 p12)
		u12 (angle p12 p11)
		p21 (cdr(assoc 10 ent2))
		y21 (car p21)
		x21 (cadr p21)
		p21 (list y21 x21 0.0)
		p22 (cdr(assoc 11 ent2))
		y22 (car p22)
		x22 (cadr p22)
		p22 (list y22 x22 0.0)
		u21 (angle p21 p22)
		u22 (angle p22 p21)
	)
	(if (< u12 u11)
		(progn
			(setq pom p11)
			(setq p11 p12)
			(setq p12 pom)
			(setq u1 u12)
		)
		(setq u1 u11)
	)
	(if (< u22 u21)
		(progn
			(setq pom p21)
			(setq p21 p22)
			(setq p22 pom)
		)
	)
        (command "line" p11 p12 "")
        (setq elmpom (entlast))
	(command "ucs" "e" (list elmpom p11))
	(setq 
		p11t (trans p11 0 1)
		p12t (trans p12 0 1)
		p21t (trans p21 0 1)
		p22t (trans p22 0 1)
	)
	(if (< (car p22t) (car p21t))
		(setq
			pom p21t
			p21t p22t
			p22t pom
		)
	)
	(if (> (car p21t) (car p11t))
		(setq prva (trans (list (car p21t) 0.0) 1 0))
		(setq prva (trans p11t 1 0))
	)
	(if (< (car p22t) (car p12t))
		(setq druga (trans (list (car p22t) 0.0) 1 0))
		(setq druga (trans p12t 1 0))
	)
	(command "ucs" "w")
	(setq upr (+ u1 (/ pi 2.0)))
	(setq dist1 (distance prva druga))
	(setq pti prva prirast 0.0 tiplin 0 p11 prva)
  (while (> dist1 prirast)
      (setq pti (polar pti u1 dist)
           ptui (polar pti upr dkratka)
          ptprs (inters pti ptui p21 p22 nil)
      )
      (if (= tiplin 0)
          (progn
            (command "line" pti ptprs "")
            (setq tiplin 1)
          );then
          (progn
            (setq ptui (polar pti (angle pti ptprs) dkratka)
                 dist2 (distance pti ptprs)
            )
            (if (> dkratka (* dist2 2))
                (command "line" pti ptui "");then
                (progn
                   (setq ptui (polar pti (angle pti ptprs) (/ dist2 2)))
                   (command "line" pti ptui "")
                );else
            );if
            (setq tiplin 0)
          );progn, else
       );if
       (setq prirast (+ (distance p11 pti) dist))
   );while
   (command "layer" "s" oldla "")
   (command "erase" elmpom "")
   (redraw elm1 4)
   (redraw elm2 4)
   (setvar "osmode" oldos)
	 (princ)
);defun
(defun *error*(msg)
	(terpri)
)
(princ)
