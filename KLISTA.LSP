(defun c:klista()
  (setvar "cmdecho" 0)
  (setvar "mirrtext" 0)
  (setq ss (ssget "x" (list (cons 0 "insert")(cons 2 "9060"))))
  (setq en (ssname ss 0))
  (setq ed (entget en))
  (setq poct (cdr(assoc 10 ed)))
  (setq razm (cdr(assoc 41 ed)))
  (setq dec (* 100.0 razm))
  (setq ypoc (car poct))
  (setq xpoc (cadr poct))
  (setq ypre "xxx")
  (setq milpre -1)
  (setq pt poct)
  (repeat 10
    (setq mil (/ ypoc 1000000.0))
    (setq mil (fix mil))
    (setq hilj (/ ypoc 1000.0))
    (setq hilj (- hilj (* mil 1000.0)))
    (setq hilj1 (fix hilj))
    (setq hiljs (itoa hilj1))
    (setq n (strlen hiljs))
    (cond
      ((= n 2)(setq hiljs (strcat "0" hiljs)))
      ((= n 1)(setq hiljs (strcat "00" hiljs)))
    )
    (setq ost (* (- hilj hilj1) 1000.0))
    (setq sto (rtos ost 2 0))
    (setq n (strlen sto))
    (cond
      ((= n 2)(setq sto (strcat "0" sto)))
      ((= n 1)(setq sto (strcat "00" sto)))
    )
    (setq t1 (list ypoc (- xpoc (* 2.0 razm))))
    (setq t2 (list (+ ypoc (* 4.0 razm)) (- xpoc (* 2.0 razm))))
    (setq t3 (list (+ ypoc (* 8.0 razm)) (- xpoc (* 2.0 razm))))
    (command "text" t1 (* 2.0 razm) "270" sto)
    (if (/= hiljs ypre)
      (command "text" t2 (* 2.0 razm) "270" hiljs)
    )
    (if (and(= milpre -1)(/= mil 0))
      (command "text" t3 (* 2.0 razm) "270" (itoa mil))
    )
    (setq ypre hiljs)
    (setq milpre mil)
    (setq pt (list (+ dec (car pt)) (cadr pt)))
    (setq ypoc (car pt))
    (setq xpoc (cadr pt))
  )
  (command "text" t2 (* 2.0 razm) "270" hiljs)
  (if (/= mil 0)
    (command "text" t3 (* 2.0 razm) "270" (itoa mil))
  )
;
;
  (setq ss nil)
  (setq ss (ssadd))
  (setq pt (list (+ (car poct) (* 900.0 razm)) (cadr poct)))
  (setq ypoc (car pt))
  (setq xpoc (cadr pt))
  (setq milpre -1)
  (setq xpre "xxx")

  (repeat 7
    (setq mil (/ xpoc 1000000.0))
    (setq mil (fix mil))
    (setq hilj (/ xpoc 1000.0))
    (setq hilj (- hilj (* mil 1000.0)))
    (setq hilj1 (fix hilj))
    (setq hiljs (itoa hilj1))
    (setq n (strlen hiljs))
    (cond
      ((= n 2)(setq hiljs (strcat "0" hiljs)))
      ((= n 1)(setq hiljs (strcat "00" hiljs)))
    )
    (setq ost (* (- hilj hilj1) 1000.0))
    (setq sto (rtos ost 2 0))
    (setq n (strlen sto))
    (cond
      ((= n 2)(setq sto (strcat "0" sto)))
      ((= n 1)(setq sto (strcat "00" sto)))
    )
    (setq t1 (list (+ ypoc (* 2.0 razm)) xpoc))
    (setq t2 (list (+ ypoc (* 2.0 razm)) (+ xpoc (* 4.0 razm))))
    (setq t3 (list (+ ypoc (* 2.0 razm)) (+ xpoc (* 8.0 razm))))
    (command "text" t1 (* 2.0 razm) "0" sto)
    (ssadd (entlast) ss)
    (if (/= hiljs ypre)
      (progn(command "text" t2 (* 2.0 razm) "0" hiljs)(ssadd (entlast) ss))
    )
    (if (and(= milpre -1)(/= mil 0))
      (progn(command "text" t3 (* 2.0 razm) "0" (itoa mil))(ssadd (entlast) ss))
    )
    (setq ypre hiljs)
    (setq milpre mil)
    (setq pt (list (car pt) (+ (cadr pt) dec)))
    (setq ypoc (car pt))
    (setq xpoc (cadr pt))
  )
  (command "text" t2 (* 2.0 razm) "0" hiljs)
  (ssadd (entlast) ss)
  (if (/= mil 0)
    (progn(command "text" t3 (* 2.0 razm) "0" (itoa mil))(ssadd (entlast) ss))
  )
  (setq t1 (list (+ (car poct) (* 450.0 razm)) (cadr poct)))
  (setq t2 (list (car t1) (+ (cadr t1) 100.0)))
  (command "mirror" ss "" t1 t2 "")
  (princ)
)
