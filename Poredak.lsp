(defun provera()
  (setq im (car pik))
  (setq op (entget im))
  (if (/= "POINT" (cdr (assoc 0 op)))
    (progn
      (princ "\n Izabrani objekt nije POINT")
      (setq pik nil)
    )
  )
)

(defun C:POREDAK(/ pik im op)
  (setq n 0)
  (if (= proredold nil) (setq proredold 0.5))
  (setq prored (getreal (strcat "\n Prored u mm <" (rtos proredold 2 2) ">:")))
  (if (= prored nil) (setq prored proredold) (setq proredold prored))
  (if (= odgold nil) (setq odgold "Dole"))
  (initget "Dole Gore")
  (setq odg (getkword (strcat "\n Gore/Dole <" odgold ">:")))
  (if (= odg nil) (setq odg odgold) (setq odgold odg))
  (if (= odg "Dole") (setq pravac -1.0) (setq pravac 1.0))
  (princ "\n Izaberi tekst:")
  (setq iz (ssget))
  (if (= iz nil) (exit))
  (setq du (sslength iz))
  (setq pik nil)
  (while (= pik nil)
    (setq pik (entsel "\n Referentni pikir:"))
    (if (/= pik nil) (provera))
  )
  (princ "\n OK")
  (setq pt (cdr (assoc 10 op)))
  (setq y (cadr pt))
  (while (/= pik nil)
    (setq pik nil)
    (while (= pik nil)
      (setq pik (entsel "\n Sledeci pikir:"))
      (if (/= pik nil) (provera))
    )
    (princ "\n OK")
    (redraw im 2)
    (setq n (+ n 1))
    (setq pt1 (cdr (assoc 10 op)))
    (setq i 0 j 0)
    (while (< i du)
      (setq im (ssname iz i))
      (setq op (entget im))
      (if (and (equal (cdr (assoc 0 op)) "TEXT") (equal (cdr (assoc 10 op)) pt1))
        (progn
          (setq ptn (list (car pt) (+ y (* pravac n (+ prored (cdr (assoc 40 op))))) (caddr pt)))
          (setq op (subst (cons 10 ptn) (assoc 10 op) op))
          (entmod op)
          (entupd im)
          (setq j (+ j 1))
        )
        (progn
        )
      )
      (setq i (+ i 1))
    )
  )
)
